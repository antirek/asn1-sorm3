ReportsCombinations DEFINITIONS IMPLICIT TAGS ::=
BEGIN

EXPORTS CombinationReport;

IMPORTS CallsRecords
    FROM ReportsConnections;

--- отчеты задач поисков по усечению отобранных данных
CombinationReport ::= CallsRecords

END
